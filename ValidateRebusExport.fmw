FME workspace ValidateRebusExport.fmw

Parameters:
- DEFINE_NET_INPUT =
- DestDataset_XLSXW =
- ErrorDistanceSAToSP =
- ErrorSpeedRouteLink =
- TIM-files =
- WarningDistanceSAToSP =
- WarningSpeedRouteLink =

Readers:
- XML_1: XML from $(DEFINE_NET_INPUT)
- XML_2: XML from $(TIM-files)
- XML_3: XML from $(TIM-files)
- XML_4: XML from $(DEFINE_NET_INPUT)

Writers:
- XLSXW_1: XLSXW to $(DestDataset_XLSXW)

Note: Description / This workspace takes in a Rebus-export file and performs a number of tests on it. / DEFINE_NET_INPUT - Define_net.xml from the Rebus-export / TIM-files - One or many tim-files with timetable data from Rebus-export / The output is a validation report in Excel-format.
AttributeFilter_4
    ATTR_NAME = fme_feature_type
    ATTR_VALUES = <Empty>,<Missing>,<Null>,<Unfiltered>,StopPoint,StopArea
    StopPoint -> DuplicateFilter
Note: Varför finns det end subletter av hållplatser?
DuplicateFilter
    INPUT_ORDERED_CHOICE = No
    KEYATTR = StopArea.Number StopPoint.LocalNumber
    UNIQUE -> FeatureMerger_2 [SUPPLIER]
FeatureMerger_2
    ATTR_ACCUM_MODE = Merge Supplier
    ATTR_CONFLICT_RES = Use Requestor
    IGNORE_NULLS = No
    JOIN_KEYS = @Value(StopPointRef.LocalNumber.StopAreaRef.Number.Number) @Value(StopArea.Number) AUTO @Value(StopPointRef.LocalNumber.LocalNumber) @Value(StopPoint.LocalNumber) AUTO
    MERGE_TYPE = Attributes and Geometry
    PROCESS_DUPS = NO
    REJECT_NULL_MISSING_KEYS = No
    SUPPLIERS_FIRST = No
    MERGED -> Sorter_2
Sorter_2
    SORT_PARM = DestinationDisplay.LineDesignation NUMERIC ASCENDING ServiceJourney.Number NUMERIC ASCENDING Call.SequenceNumber NUMERIC ASCENDING
    SORTED -> PythonCaller
Note: Create segments instread of nodes
PythonCaller
    NEW_ATTRIBUTES = FromJourneyPatternPoint ToJourneyPatternPoint DepartTime ArrivalTime FromStopAreaNumber ToStopAreaNumber FromStopAreaName ToStopAreaName FromStopPointLocalNumber ToStopPointLocalNumber
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              self.lastFeature = None

          def isSameTur(self, feature1, feature2):
              line1, line2 = feature1.getAttribute('DestinationDisplay.LineDesignation'), feature2.getAttribute('DestinationDisplay.LineDesignation')
              serviceJN1, serviceJN2 = feature1.getAttribute('ServiceJourney.Number'), feature2.getAttribute('ServiceJourney.Number')

              if line1 == line2 and serviceJN1 == serviceJN2:
                  return True
              else:
                  return False

          def input(self,feature):
              if self.lastFeature is None:
                  self.lastFeature = feature
              else:
                  if self.isSameTur(feature, self.lastFeature):
                      feature.setAttribute('FromJourneyPatternPoint', self.lastFeature.getAttribute('StopPoint.JourneyPatternPointNumber'))
                      feature.setAttribute('ToJourneyPatternPoint', feature.getAttribute('StopPoint.JourneyPatternPointNumber'))
                      feature.setAttribute('DepartTime', self.lastFeature.getAttribute('Departure.EarliestTime'))
                      feature.setAttribute('ArrivalTime', feature.getAttribute('Arrival.LatestTime'))
                      feature.setAttribute('FromStopAreaNumber', self.lastFeature.getAttribute('StopArea.Number'))
                      feature.setAttribute('ToStopAreaNumber', feature.getAttribute('StopArea.Number'))
                      feature.setAttribute('FromStopAreaName', self.lastFeature.getAttribute('StopArea.Name'))
                      feature.setAttribute('ToStopAreaName', feature.getAttribute('StopArea.Name'))
                      feature.setAttribute('FromStopPointLocalNumber', self.lastFeature.getAttribute('StopPoint.LocalNumber'))
                      feature.setAttribute('ToStopPointLocalNumber', feature.getAttribute('StopPoint.LocalNumber'))
                      self.lastFeature = feature
                      self.pyoutput(feature)
                  else:
                      self.lastFeature = feature


          def close(self):
              pass
    PYTHONSYMBOL = FeatureProcessor
    -> AttributeKeeper_2
AttributeKeeper_2
    CREATE_BULK_MODE_FEATURES = NO
    KEEP_ATTRS = ArrivalTime,DepartTime,DestinationDisplay.LineDesignation,FromJourneyPatternPoint,ServiceJourney.Number,ToJourneyPatternPoint
    -> FeatureMerger_3 [REQUESTOR]
RouteLink (reader XML_4)
    attributes: End.JourneyPatternPointRef.Number xml_char(1), End.JourneyPatternPointRef.Number.Number xml_decimal(9,0), PointsOnRouteLink.PointOnRouteLink.Location xml_char(1), PointsOnRouteLink.PointOnRouteLink.Location.Easting xml_decimal(16,8), PointsOnRouteLink.PointOnRouteLink.Location.Northing xml_decimal(16,8), PointsOnRouteLink.PointOnRouteLink.Offset xml_char(1), PointsOnRouteLink.PointOnRouteLink.Offset.DistanceFromStartMeters xml_decimal(6,2), PointsOnRouteLink.PointOnRouteLink.Type xml_char(8), PointsOnRouteLink.PointOnRouteLink{}.Location xml_char(1), PointsOnRouteLink.PointOnRouteLink{}.Location.Easting xml_decimal(17,8), PointsOnRouteLink.PointOnRouteLink{}.Location.Northing xml_decimal(17,8), PointsOnRouteLink.PointOnRouteLink{}.Offset xml_char(1), PointsOnRouteLink.PointOnRouteLink{}.Offset.DistanceFromStartMeters xml_decimal(8,2), PointsOnRouteLink.PointOnRouteLink{}.Type xml_char(8), RouteLink.DistanceMeters xml_decimal(6,0), RouteLink.SpeedLimitKmPerHour xml_decimal(4,0), Start.JourneyPatternPointRef.Number xml_char(1), Start.JourneyPatternPointRef.Number.Number xml_decimal(9,0), TraversableByTransportModes.TransportMode xml_char(1), TraversableByTransportModes.TransportMode.TransportMode xml_char(6), xml_fragment xml_xml, xml_fragment_End{} xml_char(211), xml_fragment_JourneyPatternPointRef{} xml_char(184), xml_fragment_Number{} xml_char(115), xml_fragment_Start{} xml_char(215), xml_id xml_char(22), xml_matched_element xml_char(10), xml_parent_child_pos xml_char(1), xml_parent_id xml_char(1)
    -> DuplicateFilter_2
Note: Varöfr är det ens dubletter i routelinks??
DuplicateFilter_2
    INPUT_ORDERED_CHOICE = No
    KEYATTR = End.JourneyPatternPointRef.Number.Number Start.JourneyPatternPointRef.Number.Number
    UNIQUE -> FeatureMerger_3 [SUPPLIER]
FeatureMerger_3
    ATTR_ACCUM_MODE = Merge Supplier
    ATTR_CONFLICT_RES = Use Requestor
    IGNORE_NULLS = No
    JOIN_KEYS = @Value(FromJourneyPatternPoint) @Value(Start.JourneyPatternPointRef.Number.Number) AUTO @Value(ToJourneyPatternPoint) @Value(End.JourneyPatternPointRef.Number.Number) AUTO
    MERGE_TYPE = Attributes and Geometry
    PROCESS_DUPS = NO
    REJECT_NULL_MISSING_KEYS = No
    SUPPLIERS_FIRST = No
    MERGED -> DateTimeCalculator
DateTimeCalculator
    MODE = DATETIMECALC_3_CALCULATE_INTERVAL
    OPERATION_PARAMETERS = START_DATETIME]@Value(DepartTime)]END_DATETIME]@Value(ArrivalTime)]RESULT_TYPE]SECONDS]RESULT_INTERVAL]SegmentDriveTime]FME_CONTROLLER_QUERY_FILE]transformers/dependencies/datetimecalculator/DATETIMECALC_3_CALCULATE_INTERVAL.fme
    -> Calc_timetable_speed
Calc_timetable_speed: AttributeCreator
    ATTR_TABLE = SET_TO EstimatedSpeedKmPerHour = @mult(@div(@Value(RouteLink.DistanceMeters),@Value(SegmentDriveTime)),3.6)
    -> AttributeManager_16
AttributeManager_16
    ATTR_TABLE:
      SET_TO Severity = FME_CONDITIONAL:DEFAULT_VALUE'_FME_NO_OP_'BOOL_OP;AND;COMPOSITE_TEST;1 AND 2;TEST @Value(EstimatedSpeedKmPerHour) >= $(WarningSpeedRouteLink);TEST @Value(EstimatedSpeedKmPerHour) < $(ErrorSpeedRouteLink)'WARNING'BOOL_OP;OR;COMPOSITE_TEST;1;TEST @Value(EstimatedSpeedKmPerHour) >= $(ErrorSpeedRouteLink)'ERROR'FME_NUM_CONDITIONS3___
      SET_TO TestType = AverageSpeedForRouteLinkTooHigh
    -> Has_MessageType_2
Has_MessageType_2: Tester
    BOOL_OP = OR
    COMPOSITE_TEST = 1
    TEST_CLAUSE = TEST Severity ATTRIBUTE_HAS_A_VALUE ""
    TEST_MODE = TEST
    PASSED -> NoFeaturesTester_4
NoFeaturesTester_4
    NOINPUT -> AttributeManager_18
    -> AttributeCreator_2
AttributeCreator_2
    ATTR_TABLE = SET_TO Message = Körlänk mellan hållplatserna @Value(FromJourneyPatternPoint) - @Value(ToJourneyPatternPoint) för linje @Value(DestinationDisplay.LineDesignation) tur @Value(ServiceJourney.Number) har för hög beräknad medelhastighet: @round(@Value(EstimatedSpeedKmPerHour),1)
    -> AttributeManager_17
AttributeManager_17
    ATTR_TABLE:
      RENAME_SET_VALUE Message > Felmeddelande
      RENAME_SET_VALUE EstimatedSpeedKmPerHour > Beräknad_Medelhastighet_Körlänk
      RENAME_SET_VALUE DestinationDisplay.LineDesignation > Linje
      RENAME_SET_VALUE ServiceJourney.Number > Turnummer
      RENAME_SET_VALUE FromJourneyPatternPoint > Från_HållplatsId
      RENAME_SET_VALUE ToJourneyPatternPoint > Till_HållplatsId
      RENAME_SET_VALUE DepartTime > Avgångstid
      RENAME_SET_VALUE ArrivalTime > Ankomsttid
      REMOVE End.JourneyPatternPointRef.Number
      REMOVE End.JourneyPatternPointRef.Number.Number
      REMOVE PointsOnRouteLink.PointOnRouteLink.Location
      REMOVE PointsOnRouteLink.PointOnRouteLink.Location.Easting
      REMOVE PointsOnRouteLink.PointOnRouteLink.Location.Northing
      REMOVE PointsOnRouteLink.PointOnRouteLink.Offset
      REMOVE PointsOnRouteLink.PointOnRouteLink.Offset.DistanceFromStartMeters
      REMOVE PointsOnRouteLink.PointOnRouteLink.Type
      REMOVE PointsOnRouteLink.PointOnRouteLink{}.Location
      REMOVE PointsOnRouteLink.PointOnRouteLink{}.Location.Easting
      REMOVE PointsOnRouteLink.PointOnRouteLink{}.Location.Northing
      REMOVE PointsOnRouteLink.PointOnRouteLink{}.Offset
      REMOVE PointsOnRouteLink.PointOnRouteLink{}.Offset.DistanceFromStartMeters
      REMOVE PointsOnRouteLink.PointOnRouteLink{}.Type
      RENAME_SET_VALUE RouteLink.DistanceMeters > Längd_Körlänk
      RENAME_SET_VALUE RouteLink.SpeedLimitKmPerHour > Hastighetsbegränsning_Rebus_Körlänk
      REMOVE Start.JourneyPatternPointRef.Number
      REMOVE Start.JourneyPatternPointRef.Number.Number
      REMOVE TraversableByTransportModes.TransportMode
      REMOVE TraversableByTransportModes.TransportMode.TransportMode
      REMOVE xml_fragment
      REMOVE xml_fragment_End{}
      REMOVE xml_fragment_JourneyPatternPointRef{}
      REMOVE xml_fragment_Number{}
      REMOVE xml_fragment_Start{}
      REMOVE xml_id
      REMOVE xml_matched_element
      REMOVE xml_parent_child_pos
      REMOVE xml_parent_id
      RENAME_SET_VALUE SegmentDriveTime > Planerad_Körtid
      RENAME_SET_VALUE Severity > Allvarlighetsgrad
      RENAME_SET_VALUE TestType > TestTyp
      SET_TO sum = 1
    -> Sorter_3
Sorter_3
    SORT_PARM = Beräknad_Medelhastighet_Körlänk NUMERIC DESCENDING
    SORTED -> ExcelStyler_4
ExcelStyler_4
    ATTRS_TO_STYLE = Allvarlighetsgrad
    BACKGROUND_COLOR = FME_CONDITIONAL:DEFAULT_VALUE''BOOL_OP;OR;COMPOSITE_TEST;1;TEST @Value(Allvarlighetsgrad) = WARNING'1,0.827451,0.529412'BOOL_OP;OR;COMPOSITE_TEST;1;TEST @Value(Allvarlighetsgrad) = ERROR'1,0.501961,0.501961'FME_NUM_CONDITIONS3___
    ROW_OR_CELL = cell
    ExcelStyled -> RouteLinkSpeedTooHigh (writer XLSXW_1)
    ExcelStyled -> AttributeKeeper
AttributeManager_18
    ATTR_TABLE:
      REMOVE EstimatedSpeedKmPerHour
      REMOVE DestinationDisplay.LineDesignation
      REMOVE ServiceJourney.Number
      REMOVE FromJourneyPatternPoint
      REMOVE ToJourneyPatternPoint
      REMOVE DepartTime
      REMOVE ArrivalTime
      REMOVE End.JourneyPatternPointRef.Number
      REMOVE End.JourneyPatternPointRef.Number.Number
      REMOVE PointsOnRouteLink.PointOnRouteLink.Location
      REMOVE PointsOnRouteLink.PointOnRouteLink.Location.Easting
      REMOVE PointsOnRouteLink.PointOnRouteLink.Location.Northing
      REMOVE PointsOnRouteLink.PointOnRouteLink.Offset
      REMOVE PointsOnRouteLink.PointOnRouteLink.Offset.DistanceFromStartMeters
      REMOVE PointsOnRouteLink.PointOnRouteLink.Type
      REMOVE PointsOnRouteLink.PointOnRouteLink{}.Location
      REMOVE PointsOnRouteLink.PointOnRouteLink{}.Location.Easting
      REMOVE PointsOnRouteLink.PointOnRouteLink{}.Location.Northing
      REMOVE PointsOnRouteLink.PointOnRouteLink{}.Offset
      REMOVE PointsOnRouteLink.PointOnRouteLink{}.Offset.DistanceFromStartMeters
      REMOVE PointsOnRouteLink.PointOnRouteLink{}.Type
      REMOVE RouteLink.DistanceMeters
      REMOVE RouteLink.SpeedLimitKmPerHour
      REMOVE Start.JourneyPatternPointRef.Number
      REMOVE Start.JourneyPatternPointRef.Number.Number
      REMOVE TraversableByTransportModes.TransportMode
      REMOVE TraversableByTransportModes.TransportMode.TransportMode
      REMOVE xml_fragment
      REMOVE xml_fragment_End{}
      REMOVE xml_fragment_JourneyPatternPointRef{}
      REMOVE xml_fragment_Number{}
      REMOVE xml_fragment_Start{}
      REMOVE xml_id
      REMOVE xml_matched_element
      REMOVE xml_parent_child_pos
      REMOVE xml_parent_id
      REMOVE SegmentDriveTime
      RENAME_SET_VALUE Severity > Allvarlighetsgrad
      RENAME_SET_VALUE TestType > TestTyp
      SET_TO sum = 0
    -> AttributeKeeper

Bookmark: Readers Tidtabellfiler
Call (reader XML_2)
    attributes: Arrival xml_char(1), Arrival.DayOffset xml_decimal(2,0), Arrival.LatestTime xml_char(9), Arrival.TypeOfArrival xml_char(13), Call.IsTimingPoint xml_char(2), Call.SequenceNumber xml_decimal(3,0), ChangeFromRules.ChangeFromRule.FeederJourneyFilter.JourneyOnDirectionOfLineDef.DirectionOfLineRef.Gid xml_char(1), ChangeFromRules.ChangeFromRule.FeederJourneyFilter.JourneyOnDirectionOfLineDef.DirectionOfLineRef.Gid.Gid xml_decimal(17,0), ChangeFromRules.ChangeFromRule.FeederJourneyFilter.JourneyOnDirectionOfLineDef.MaxOffsetDuration xml_char(6), ChangeFromRules.ChangeFromRule.FeederStopRef.StopAreaRef.Gid xml_char(1), ChangeFromRules.ChangeFromRule.FeederStopRef.StopAreaRef.Gid.Gid xml_decimal(17,0), ChangeFromRules.ChangeFromRule.MaximumWaitTimeDuration xml_char(6), ChangeFromRules.ChangeFromRule{}.FeederJourneyFilter.JourneyOnDirectionOfLineDef.DirectionOfLineRef.Gid xml_char(1), ChangeFromRules.ChangeFromRule{}.FeederJourneyFilter.JourneyOnDirectionOfLineDef.DirectionOfLineRef.Gid.Gid xml_decimal(17,0), ChangeFromRules.ChangeFromRule{}.FeederJourneyFilter.JourneyOnDirectionOfLineDef.MaxOffsetDuration xml_char(6), ChangeFromRules.ChangeFromRule{}.FeederStopRef.StopAreaRef.Gid xml_char(1), ChangeFromRules.ChangeFromRule{}.FeederStopRef.StopAreaRef.Gid.Gid xml_decimal(17,0), ChangeFromRules.ChangeFromRule{}.MaximumWaitTimeDuration xml_char(5), Departure xml_char(1), Departure.DayOffset xml_decimal(2,0), Departure.EarliestTime xml_char(9), Departure.TypeOfDeparture xml_char(12), NewDestinationDisplay.ExternalKeys.Key xml_char(1), NewDestinationDisplay.ExternalKeys.Key.DeviceName xml_char(9), NewDestinationDisplay.ExternalKeys.Key.ParameterData xml_char(20), NewDestinationDisplay.PrimaryDestination.Text xml_char(1), NewDestinationDisplay.PrimaryDestination.Text.Name xml_char(18), NewDestinationDisplay.ProductName xml_char(5), Notes.Note xml_char(1), Notes.Note.ConcernsDepartures xml_boolean,
      Notes.Note.IsExposedInDynamicMedia xml_char(2), Notes.Note.Text xml_char(47), ServiceJourney.ExternalSourceComment xml_char(8), ServiceJourney.Number xml_decimal(4,0), ServiceJourney.TransportMode xml_char(5), StopPointRef.LocalNumber.LocalNumber xml_decimal(3,0), StopPointRef.LocalNumber.StopAreaRef.Number xml_char(1), StopPointRef.LocalNumber.StopAreaRef.Number.Number xml_decimal(7,0), TimetableVersion.DocumentLayoutVersion xml_char(7), TimetableVersion.ModificationType xml_char(7), TimetableVersion.xmlns xml_char(32), TimetableVersion.xsd xml_char(33), TimetableVersion.xsi xml_char(42), xml_fragment xml_xml, xml_id xml_char(21), xml_matched_element xml_char(5), xml_parent_child_pos xml_char(1), xml_parent_id xml_char(1)
    -> FeatureMerger [REQUESTOR]
DestinationDisplay (reader XML_3)
    attributes: DestinationDisplay.LineDesignation xml_decimal(4,0), ExternalKeys.Key xml_char(1), ExternalKeys.Key.DeviceName xml_char(9), ExternalKeys.Key.ParameterData xml_char(19), PrimaryDestination.Text xml_char(1), PrimaryDestination.Text.Name xml_char(29), ServiceJourney.ExternalSourceComment xml_char(8), ServiceJourney.Number xml_decimal(4,0), ServiceJourney.TransportMode xml_char(5), TimetableVersion.DocumentLayoutVersion xml_char(7), TimetableVersion.ModificationType xml_char(7), TimetableVersion.xmlns xml_char(32), TimetableVersion.xsd xml_char(33), TimetableVersion.xsi xml_char(42), xml_fragment xml_xml, xml_fragment_PrimaryDestination{} xml_char(194), xml_fragment_Text{} xml_char(129), xml_id xml_char(33), xml_matched_element xml_char(19), xml_parent_child_pos xml_char(1), xml_parent_id xml_char(1)
    -> FeatureMerger [SUPPLIER]

Bookmark: Preprocess timetable data
FeatureMerger
    ATTR_ACCUM_MODE = Merge Supplier
    ATTR_CONFLICT_RES = Use Requestor
    IGNORE_NULLS = No
    JOIN_KEYS = @Value(ServiceJourney.Number) @Value(ServiceJourney.Number) AUTO @Value(fme_basename) @Value(fme_basename) AUTO
    MERGE_TYPE = Attributes Only
    PROCESS_DUPS = NO
    REJECT_NULL_MISSING_KEYS = No
    SUPPLIERS_FIRST = No
    MERGED -> AttributeManager_15
AttributeManager_15
    ATTR_TABLE:
      REMOVE Departure.TypeOfDeparture
      REMOVE Arrival.DayOffset
      REMOVE Arrival.TypeOfArrival
      REMOVE Call.IsTimingPoint
      REMOVE Departure.DayOffset
      REMOVE ChangeFromRules.ChangeFromRule.FeederJourneyFilter.JourneyOnDirectionOfLineDef.DirectionOfLineRef.Gid
      REMOVE ChangeFromRules.ChangeFromRule.FeederJourneyFilter.JourneyOnDirectionOfLineDef.DirectionOfLineRef.Gid.Gid
      REMOVE ChangeFromRules.ChangeFromRule.FeederJourneyFilter.JourneyOnDirectionOfLineDef.MaxOffsetDuration
      REMOVE ChangeFromRules.ChangeFromRule.FeederStopRef.StopAreaRef.Gid
      REMOVE ChangeFromRules.ChangeFromRule.FeederStopRef.StopAreaRef.Gid.Gid
      REMOVE ChangeFromRules.ChangeFromRule.MaximumWaitTimeDuration
      REMOVE ChangeFromRules.ChangeFromRule{}.FeederJourneyFilter.JourneyOnDirectionOfLineDef.DirectionOfLineRef.Gid
      REMOVE ChangeFromRules.ChangeFromRule{}.FeederJourneyFilter.JourneyOnDirectionOfLineDef.DirectionOfLineRef.Gid.Gid
      REMOVE ChangeFromRules.ChangeFromRule{}.FeederJourneyFilter.JourneyOnDirectionOfLineDef.MaxOffsetDuration
      REMOVE ChangeFromRules.ChangeFromRule{}.FeederStopRef.StopAreaRef.Gid
      REMOVE ChangeFromRules.ChangeFromRule{}.FeederStopRef.StopAreaRef.Gid.Gid
      REMOVE ChangeFromRules.ChangeFromRule{}.MaximumWaitTimeDuration
      REMOVE Departure
      REMOVE NewDestinationDisplay.ExternalKeys.Key
      REMOVE NewDestinationDisplay.ExternalKeys.Key.DeviceName
      REMOVE NewDestinationDisplay.ExternalKeys.Key.ParameterData
      REMOVE NewDestinationDisplay.PrimaryDestination.Text
      REMOVE NewDestinationDisplay.PrimaryDestination.Text.Name
      REMOVE NewDestinationDisplay.ProductName
      REMOVE Notes.Note
      REMOVE Notes.Note.ConcernsDepartures
      REMOVE Notes.Note.IsExposedInDynamicMedia
      REMOVE StopPointRef.LocalNumber.StopAreaRef.Number
      REMOVE TimetableVersion.DocumentLayoutVersion
      REMOVE TimetableVersion.ModificationType
      REMOVE TimetableVersion.xmlns
      REMOVE TimetableVersion.xsd
      REMOVE TimetableVersion.xsi
      REMOVE xml_fragment
      REMOVE xml_id
      REMOVE xml_matched_element
      REMOVE xml_parent_child_pos
      REMOVE xml_parent_id
      REMOVE ExternalKeys.Key
      REMOVE ExternalKeys.Key.DeviceName
      REMOVE ExternalKeys.Key.ParameterData
      REMOVE PrimaryDestination.Text
      REMOVE xml_fragment_PrimaryDestination{}
      REMOVE xml_fragment_Text{}
      REMOVE Arrival
    -> FeatureMerger_2 [REQUESTOR]

Bookmark: Readers
StopArea (reader XML_1)
    attributes: Centroid xml_char(1), Centroid.Easting xml_decimal(8,0), Centroid.Northing xml_decimal(8,0), StopArea.Abbreviation xml_char(8), StopArea.DefaultInterchangeDuration xml_char(6), StopArea.InterchangePriority xml_decimal(3,0), StopArea.Name xml_char(41), StopArea.Number xml_decimal(7,0), StopArea.ShortName xml_char(17), StopArea.Type xml_char(15), StopPoints.StopPoint.Designation xml_char(2), StopPoints.StopPoint.JourneyPatternPointNumber xml_decimal(9,0), StopPoints.StopPoint.Keys.Key{}.KeyValues.KeyValue xml_char(1), StopPoints.StopPoint.Keys.Key{}.KeyValues.KeyValue.Value xml_char(13), StopPoints.StopPoint.Keys.Key{}.TypeName xml_char(30), StopPoints.StopPoint.LengthMeters xml_decimal(3,0), StopPoints.StopPoint.LocalNumber xml_decimal(2,0), StopPoints.StopPoint.Location xml_char(1), StopPoints.StopPoint.Location.Easting xml_decimal(8,0), StopPoints.StopPoint.Location.Northing xml_decimal(8,0), StopPoints.StopPoint.Name xml_char(34), StopPoints.StopPoint.Orientation xml_decimal(4,0), StopPoints.StopPoint.Type xml_char(8), StopPoints.StopPoint.ZoneRefs.ZoneRef{} xml_char(1), StopPoints.StopPoint.ZoneRefs.ZoneRef{}.ZoneNumber xml_decimal(5,0), StopPoints.StopPoint.ZoneRefs.ZoneRef{}.ZoneType xml_char(13), StopPoints.StopPoint{}.Designation xml_char(3), StopPoints.StopPoint{}.JourneyPatternPointNumber xml_decimal(9,0), StopPoints.StopPoint{}.Keys.Key{}.KeyValues.KeyValue xml_char(1), StopPoints.StopPoint{}.Keys.Key{}.KeyValues.KeyValue.Value xml_char(13),
      StopPoints.StopPoint{}.Keys.Key{}.TypeName xml_char(30), StopPoints.StopPoint{}.LengthMeters xml_decimal(4,0), StopPoints.StopPoint{}.LocalNumber xml_decimal(3,0), StopPoints.StopPoint{}.Location xml_char(1), StopPoints.StopPoint{}.Location.Easting xml_decimal(10,0), StopPoints.StopPoint{}.Location.Northing xml_decimal(10,0), StopPoints.StopPoint{}.Name xml_char(41), StopPoints.StopPoint{}.Orientation xml_decimal(4,0), StopPoints.StopPoint{}.Type xml_char(9), StopPoints.StopPoint{}.ZoneRefs.ZoneRef{} xml_char(1), StopPoints.StopPoint{}.ZoneRefs.ZoneRef{}.ZoneNumber xml_decimal(5,0), StopPoints.StopPoint{}.ZoneRefs.ZoneRef{}.ZoneType xml_char(13), ValidDatePeriod xml_char(1), ValidDatePeriod.ValidFromDate xml_char(11), xml_fragment xml_xml, xml_id xml_char(21), xml_matched_element xml_char(9), xml_parent_child_pos xml_char(1), xml_parent_id xml_char(1)
    -> AttributeManager
StopPoint (reader XML_1)
    attributes: Keys.Key{}.KeyValues.KeyValue xml_char(1), Keys.Key{}.KeyValues.KeyValue.Value xml_char(13), Keys.Key{}.TypeName xml_char(30), Location xml_char(1), Location.Easting xml_decimal(10,0), Location.Northing xml_decimal(10,0), StopPoint.Designation xml_char(3), StopPoint.JourneyPatternPointNumber xml_decimal(9,0), StopPoint.LengthMeters xml_decimal(4,0), StopPoint.LocalNumber xml_decimal(3,0), StopPoint.Name xml_char(41), StopPoint.Orientation xml_decimal(4,0), StopPoint.Type xml_char(9), ZoneRefs.ZoneRef{} xml_char(1), ZoneRefs.ZoneRef{}.ZoneNumber xml_decimal(5,0), ZoneRefs.ZoneRef{}.ZoneType xml_char(13), xml_fragment xml_xml, xml_id xml_char(27), xml_matched_element xml_char(10), xml_parent_child_pos xml_decimal(3,0), xml_parent_id xml_char(21)
    -> AttributeManager_2

Bookmark: Generate Geomeries in SWEREF99TM for StopAreas and StopPoints
AttributeManager
    ATTR_TABLE:
      SET_TO N = @Value(Centroid.Northing)
      SET_TO E = @Value(Centroid.Easting)
    -> VertexCreator
AttributeManager_2
    ATTR_TABLE:
      SET_TO N = @Value(Location.Northing)
      SET_TO E = @Value(Location.Easting)
    -> VertexCreator
VertexCreator
    MEASURE_TYPE = Continuous
    MISSING_VAL_MODE = Compute
    MODE_NAME = Add Point
    XVAL = @Value(E)
    YVAL = @Value(N)
    -> CoordinateSystemSetter
CoordinateSystemSetter
    COORDSYS = EPSG:2400
    -> Reprojector
Reprojector
    DEST = EPSG:3006
    INTERPOLATION_TYPE_NAME = Nearest Neighbor
    RASTER_CELL_SIZE = Preserve Cells
    RASTER_TOLERANCE = 0.0
    SOURCE = Read from feature
    REPROJECTED -> PointOnAreaOverlayer [POINT]
    REPROJECTED -> AttributeFilter
    REPROJECTED -> AttributeFilter_4

Bookmark: Test if centroid is more than X meters from the stop point, write results to Excel and make sure that if no features failed the test -> the summary still gets a feature to include in order to create a row with 0 errors.
AttributeFilter
    ATTR_NAME = fme_feature_type
    ATTR_VALUES = <Empty>,<Missing>,<Null>,<Unfiltered>,StopPoint,StopArea
    StopPoint -> FeatureJoiner [LEFT]
    StopArea -> FeatureJoiner [RIGHT]
FeatureJoiner
    ATTR_CONFLICT_RES = Use Left
    GEOMETRY_HANDLING = Use Left
    JOIN_KEYS = xml_parent_id xml_id AUTO
    JOIN_MODE = Inner
    JOINED -> AttributeManager_3
AttributeManager_3
    ATTR_TABLE = SET_TO DistanceToCentroid = @round(@sqrt(@add(@pow(@sub(@Value(Location.Easting),@Value(Centroid.Easting)),2),@pow(@sub(@Value(Location.Northing),@Value(Centroid.Northing)),2))),0)
    -> AttributeManager_4
AttributeManager_4
    ATTR_TABLE:
      SET_TO Severity = FME_CONDITIONAL:DEFAULT_VALUE'_FME_NO_OP_'BOOL_OP;AND;COMPOSITE_TEST;1 AND 2;TEST @Value(DistanceToCentroid) > $(WarningDistanceSAToSP);TEST @Value(DistanceToCentroid) < $(ErrorDistanceSAToSP)'WARNING'BOOL_OP;OR;COMPOSITE_TEST;1;TEST @Value(DistanceToCentroid) > $(ErrorDistanceSAToSP)'ERROR'FME_NUM_CONDITIONS3___
      SET_TO TestType = StopPointsIsWithinDistanceOfStopArea
    -> Has_MessageType
Has_MessageType: Tester
    BOOL_OP = OR
    COMPOSITE_TEST = 1
    TEST_CLAUSE = TEST Severity ATTRIBUTE_HAS_A_VALUE ""
    TEST_MODE = TEST
    PASSED -> NoFeaturesTester_3
NoFeaturesTester_3
    NOINPUT -> AttributeManager_11
    NOINPUT -> AttributeManager_12
    -> AttributeCreator
AttributeCreator
    ATTR_TABLE = SET_TO Message = Hållplatsläge @Value(StopPoint.Designation) för hållplats @Value(StopPoint.Name) är @Value(DistanceToCentroid) meter från hållplatsens centrumkoordinat.
    -> AttributeManager_5
AttributeManager_5
    ATTR_TABLE:
      REMOVE Message
      REMOVE Centroid
      REMOVE StopArea.Abbreviation
      REMOVE StopArea.DefaultInterchangeDuration
      REMOVE StopArea.InterchangePriority
      REMOVE StopArea.Name
      REMOVE StopArea.ShortName
      REMOVE StopArea.Type
      REMOVE StopPoints.StopPoint.Designation
      REMOVE StopPoints.StopPoint.JourneyPatternPointNumber
      REMOVE StopPoints.StopPoint.Keys.Key{}.KeyValues.KeyValue
      REMOVE StopPoints.StopPoint.Keys.Key{}.KeyValues.KeyValue.Value
      REMOVE StopPoints.StopPoint.Keys.Key{}.TypeName
      REMOVE StopPoints.StopPoint.LengthMeters
      REMOVE StopPoints.StopPoint.LocalNumber
      REMOVE StopPoints.StopPoint.Location
      REMOVE StopPoints.StopPoint.Location.Easting
      REMOVE StopPoints.StopPoint.Location.Northing
      REMOVE StopPoints.StopPoint.Orientation
      REMOVE StopPoints.StopPoint.Type
      REMOVE StopPoints.StopPoint.ZoneRefs.ZoneRef{}
      REMOVE StopPoints.StopPoint.ZoneRefs.ZoneRef{}.ZoneNumber
      REMOVE StopPoints.StopPoint.ZoneRefs.ZoneRef{}.ZoneType
      REMOVE StopPoints.StopPoint{}.Designation
      REMOVE StopPoints.StopPoint{}.JourneyPatternPointNumber
      REMOVE StopPoints.StopPoint{}.Keys.Key{}.KeyValues.KeyValue
      REMOVE StopPoints.StopPoint{}.Keys.Key{}.KeyValues.KeyValue.Value
      REMOVE StopPoints.StopPoint{}.Keys.Key{}.TypeName
      REMOVE StopPoints.StopPoint{}.LengthMeters
      REMOVE StopPoints.StopPoint{}.LocalNumber
      REMOVE StopPoints.StopPoint{}.Location
      REMOVE StopPoints.StopPoint{}.Location.Easting
      REMOVE StopPoints.StopPoint{}.Location.Northing
      REMOVE StopPoints.StopPoint{}.Name
      REMOVE StopPoints.StopPoint{}.Orientation
      REMOVE StopPoints.StopPoint{}.Type
      REMOVE StopPoints.StopPoint{}.ZoneRefs.ZoneRef{}
      REMOVE StopPoints.StopPoint{}.ZoneRefs.ZoneRef{}.ZoneNumber
      REMOVE StopPoints.StopPoint{}.ZoneRefs.ZoneRef{}.ZoneType
      REMOVE ValidDatePeriod
      REMOVE ValidDatePeriod.ValidFromDate
      REMOVE xml_fragment
      REMOVE xml_id
      REMOVE xml_matched_element
      REMOVE xml_parent_child_pos
      REMOVE xml_parent_id
      REMOVE fme_feature_type
      REMOVE N
      REMOVE E
      REMOVE Keys.Key{}.KeyValues.KeyValue
      REMOVE Keys.Key{}.KeyValues.KeyValue.Value
      REMOVE Keys.Key{}.TypeName
      REMOVE Location
      REMOVE StopPoint.LengthMeters
      REMOVE StopPoint.LocalNumber
      REMOVE StopPoint.Orientation
      REMOVE StopPoint.Type
      REMOVE ZoneRefs.ZoneRef{}
      REMOVE ZoneRefs.ZoneRef{}.ZoneNumber
      REMOVE ZoneRefs.ZoneRef{}.ZoneType
      RENAME_SET_VALUE StopPoint.Name > Hållplatslägesnamn
      RENAME_SET_VALUE StopPoint.Designation > Hållplatsläge
      RENAME_SET_VALUE StopPoint.JourneyPatternPointNumber > Hållplatslägesnummer
      RENAME_SET_VALUE DistanceToCentroid > AvståndTillCentrumpunktMeter
      REMOVE StopPoints.StopPoint.Name
      RENAME_SET_VALUE Location.Easting > HållplatslägeÖstligKoordinat
      RENAME_SET_VALUE Location.Northing > HållplatslägeNordligKoordinat
      RENAME_SET_VALUE Centroid.Easting > CentrumkoordinatÖstlig
      RENAME_SET_VALUE Centroid.Northing > CentrumkoordinatNordlig
      RENAME_SET_VALUE StopArea.Number > Hållplatsnummer
      RENAME_SET_VALUE TestType > TestTyp
      RENAME_SET_VALUE Severity > Allvarlighetsgrad
      SET_TO Felmeddelande = Hållplatsläge @Value(Hållplatslägesnamn) @Value(Hållplatsläge) med ID: @Value(Hållplatslägesnummer) ligger @Value(AvståndTillCentrumpunktMeter) meter från hållplatsens centrumpunkt.
      SET_TO sum = 1
    -> Sorter
Sorter
    SORT_PARM = AvståndTillCentrumpunktMeter NUMERIC DESCENDING
    SORTED -> ExcelStyler_2
ExcelStyler_2
    ATTRS_TO_STYLE = Allvarlighetsgrad
    BACKGROUND_COLOR = FME_CONDITIONAL:DEFAULT_VALUE''BOOL_OP;OR;COMPOSITE_TEST;1;TEST @Value(Allvarlighetsgrad) = WARNING'1,0.827451,0.529412'BOOL_OP;OR;COMPOSITE_TEST;1;TEST @Value(Allvarlighetsgrad) = ERROR'1,0.501961,0.501961'FME_NUM_CONDITIONS3___
    ROW_OR_CELL = cell
    ExcelStyled -> StopPointsIsWithinDistanceOfStopArea (writer XLSXW_1)
    ExcelStyled -> AttributeKeeper
AttributeManager_11
    ATTR_TABLE:
      REMOVE Centroid
      REMOVE Centroid.Easting
      REMOVE Centroid.Northing
      REMOVE StopArea.Abbreviation
      REMOVE StopArea.DefaultInterchangeDuration
      REMOVE StopArea.InterchangePriority
      REMOVE StopArea.Name
      REMOVE StopArea.Number
      REMOVE StopArea.ShortName
      REMOVE StopArea.Type
      REMOVE StopPoints.StopPoint.Designation
      REMOVE StopPoints.StopPoint.JourneyPatternPointNumber
      REMOVE StopPoints.StopPoint.Keys.Key{}.KeyValues.KeyValue
      REMOVE StopPoints.StopPoint.Keys.Key{}.KeyValues.KeyValue.Value
      REMOVE StopPoints.StopPoint.Keys.Key{}.TypeName
      REMOVE StopPoints.StopPoint.LengthMeters
      REMOVE StopPoints.StopPoint.LocalNumber
      REMOVE StopPoints.StopPoint.Location
      REMOVE StopPoints.StopPoint.Location.Easting
      REMOVE StopPoints.StopPoint.Location.Northing
      REMOVE StopPoints.StopPoint.Name
      REMOVE StopPoints.StopPoint.Orientation
      REMOVE StopPoints.StopPoint.Type
      REMOVE StopPoints.StopPoint.ZoneRefs.ZoneRef{}
      REMOVE StopPoints.StopPoint.ZoneRefs.ZoneRef{}.ZoneNumber
      REMOVE StopPoints.StopPoint.ZoneRefs.ZoneRef{}.ZoneType
      REMOVE StopPoints.StopPoint{}.Designation
      REMOVE StopPoints.StopPoint{}.JourneyPatternPointNumber
      REMOVE StopPoints.StopPoint{}.Keys.Key{}.KeyValues.KeyValue
      REMOVE StopPoints.StopPoint{}.Keys.Key{}.KeyValues.KeyValue.Value
      REMOVE StopPoints.StopPoint{}.Keys.Key{}.TypeName
      REMOVE StopPoints.StopPoint{}.LengthMeters
      REMOVE StopPoints.StopPoint{}.LocalNumber
      REMOVE StopPoints.StopPoint{}.Location
      REMOVE StopPoints.StopPoint{}.Location.Easting
      REMOVE StopPoints.StopPoint{}.Location.Northing
      REMOVE StopPoints.StopPoint{}.Name
      REMOVE StopPoints.StopPoint{}.Orientation
      REMOVE StopPoints.StopPoint{}.Type
      REMOVE StopPoints.StopPoint{}.ZoneRefs.ZoneRef{}
      REMOVE StopPoints.StopPoint{}.ZoneRefs.ZoneRef{}.ZoneNumber
      REMOVE StopPoints.StopPoint{}.ZoneRefs.ZoneRef{}.ZoneType
      REMOVE ValidDatePeriod
      REMOVE ValidDatePeriod.ValidFromDate
      REMOVE xml_fragment
      REMOVE xml_id
      REMOVE xml_matched_element
      REMOVE xml_parent_child_pos
      REMOVE xml_parent_id
      REMOVE fme_feature_type
      REMOVE N
      REMOVE E
      REMOVE Keys.Key{}.KeyValues.KeyValue
      REMOVE Keys.Key{}.KeyValues.KeyValue.Value
      REMOVE Keys.Key{}.TypeName
      REMOVE Location
      REMOVE Location.Easting
      REMOVE Location.Northing
      REMOVE StopPoint.Designation
      REMOVE StopPoint.JourneyPatternPointNumber
      REMOVE StopPoint.LengthMeters
      REMOVE StopPoint.LocalNumber
      REMOVE StopPoint.Name
      REMOVE StopPoint.Orientation
      REMOVE StopPoint.Type
      REMOVE ZoneRefs.ZoneRef{}
      REMOVE ZoneRefs.ZoneRef{}.ZoneNumber
      REMOVE ZoneRefs.ZoneRef{}.ZoneType
      REMOVE no_features
      SET_TO Allvarlighetsgrad = WARNING
      SET_TO TestTyp = StopPointsIsWithinDistanceOfStopArea
      REMOVE DistanceToCentroid
      REMOVE Severity
      REMOVE TestType
      SET_TO sum = 0
    -> AttributeKeeper
AttributeManager_12
    ATTR_TABLE:
      REMOVE Centroid
      REMOVE Centroid.Easting
      REMOVE Centroid.Northing
      REMOVE StopArea.Abbreviation
      REMOVE StopArea.DefaultInterchangeDuration
      REMOVE StopArea.InterchangePriority
      REMOVE StopArea.Name
      REMOVE StopArea.Number
      REMOVE StopArea.ShortName
      REMOVE StopArea.Type
      REMOVE StopPoints.StopPoint.Designation
      REMOVE StopPoints.StopPoint.JourneyPatternPointNumber
      REMOVE StopPoints.StopPoint.Keys.Key{}.KeyValues.KeyValue
      REMOVE StopPoints.StopPoint.Keys.Key{}.KeyValues.KeyValue.Value
      REMOVE StopPoints.StopPoint.Keys.Key{}.TypeName
      REMOVE StopPoints.StopPoint.LengthMeters
      REMOVE StopPoints.StopPoint.LocalNumber
      REMOVE StopPoints.StopPoint.Location
      REMOVE StopPoints.StopPoint.Location.Easting
      REMOVE StopPoints.StopPoint.Location.Northing
      REMOVE StopPoints.StopPoint.Name
      REMOVE StopPoints.StopPoint.Orientation
      REMOVE StopPoints.StopPoint.Type
      REMOVE StopPoints.StopPoint.ZoneRefs.ZoneRef{}
      REMOVE StopPoints.StopPoint.ZoneRefs.ZoneRef{}.ZoneNumber
      REMOVE StopPoints.StopPoint.ZoneRefs.ZoneRef{}.ZoneType
      REMOVE StopPoints.StopPoint{}.Designation
      REMOVE StopPoints.StopPoint{}.JourneyPatternPointNumber
      REMOVE StopPoints.StopPoint{}.Keys.Key{}.KeyValues.KeyValue
      REMOVE StopPoints.StopPoint{}.Keys.Key{}.KeyValues.KeyValue.Value
      REMOVE StopPoints.StopPoint{}.Keys.Key{}.TypeName
      REMOVE StopPoints.StopPoint{}.LengthMeters
      REMOVE StopPoints.StopPoint{}.LocalNumber
      REMOVE StopPoints.StopPoint{}.Location
      REMOVE StopPoints.StopPoint{}.Location.Easting
      REMOVE StopPoints.StopPoint{}.Location.Northing
      REMOVE StopPoints.StopPoint{}.Name
      REMOVE StopPoints.StopPoint{}.Orientation
      REMOVE StopPoints.StopPoint{}.Type
      REMOVE StopPoints.StopPoint{}.ZoneRefs.ZoneRef{}
      REMOVE StopPoints.StopPoint{}.ZoneRefs.ZoneRef{}.ZoneNumber
      REMOVE StopPoints.StopPoint{}.ZoneRefs.ZoneRef{}.ZoneType
      REMOVE ValidDatePeriod
      REMOVE ValidDatePeriod.ValidFromDate
      REMOVE xml_fragment
      REMOVE xml_id
      REMOVE xml_matched_element
      REMOVE xml_parent_child_pos
      REMOVE xml_parent_id
      REMOVE fme_feature_type
      REMOVE N
      REMOVE E
      REMOVE Keys.Key{}.KeyValues.KeyValue
      REMOVE Keys.Key{}.KeyValues.KeyValue.Value
      REMOVE Keys.Key{}.TypeName
      REMOVE Location
      REMOVE Location.Easting
      REMOVE Location.Northing
      REMOVE StopPoint.Designation
      REMOVE StopPoint.JourneyPatternPointNumber
      REMOVE StopPoint.LengthMeters
      REMOVE StopPoint.LocalNumber
      REMOVE StopPoint.Name
      REMOVE StopPoint.Orientation
      REMOVE StopPoint.Type
      REMOVE ZoneRefs.ZoneRef{}
      REMOVE ZoneRefs.ZoneRef{}.ZoneNumber
      REMOVE ZoneRefs.ZoneRef{}.ZoneType
      REMOVE no_features
      SET_TO Allvarlighetsgrad = ERROR
      SET_TO TestTyp = StopPointsIsWithinDistanceOfStopArea
      REMOVE DistanceToCentroid
      REMOVE Severity
      REMOVE TestType
      SET_TO sum = 0
    -> AttributeKeeper

Bookmark: Witers
StopPointsIsWithinDistanceOfStopArea (writer XLSXW_1)
    attributes: Allvarlighetsgrad string(15), Felmeddelande string(100), Hållplatslägesnamn string(41), Hållplatsläge string(12), Hållplatslägesnummer number(20), AvståndTillCentrumpunktMeter number(30), HållplatslägeÖstligKoordinat number(30), HållplatslägeNordligKoordinat number(30), CentrumkoordinatÖstlig number(30), CentrumkoordinatNordlig number(30), Hållplatsnummer number(20), TestTyp string(50), Allvarlighetsgrad.formatting string(200)

Bookmark: Test if coordinate is within a created polygon and separe StopAreas from StopPoints
Creator_2
    COORDSYS = EPSG:3006
    GEOM = <?xml version="1.0" encoding="US_ASCII" standalone="no" ?><geometry><polygon><line><coord x="205329" y="6120677"/><coord x="772625" y="6120677"/><coord x="772625" y="6929823"/><coord x="205329" y="6929823"/><coord x="205329" y="6120677"/></line></polygon></geometry>
    GEOMTYPE = Geometry Object
    NUM = 1
    CREATED -> PointOnAreaOverlayer [AREA]
PointOnAreaOverlayer
    ATTR_ACCUM_MODE = Merge Incoming
    ATTR_CONFLICT_RES = Use Original
    CANDIDATE_LIST_ATTRS_TO_INCLUDE_MODE = Selected Attributes
    DEAGGREGATE_INPUT = Yes
    OV_ATTR = _overlaps
    POLYS_FIRST = No
    POINT -> Is_Invalid_Coordinate
Is_Invalid_Coordinate: Tester
    BOOL_OP = OR
    COMPOSITE_TEST = 1
    TEST_CLAUSE = TEST @Value(_overlaps) = 0
    TEST_MODE = TEST
    PASSED -> AttributeFilter_2
AttributeFilter_2
    ATTR_NAME = fme_feature_type
    ATTR_VALUES = <Empty>,<Missing>,<Null>,<Unfiltered>,StopPoint,StopArea
    StopPoint -> NoFeaturesTester
    StopArea -> NoFeaturesTester_2

Bookmark: Write results to Excel and make sure that if no features failed the test -> the summary still gets a feature to include in order to create a row with 0 errors.
NoFeaturesTester
    NOINPUT -> AttributeManager_9
    -> AttributeManager_6
AttributeManager_9
    ATTR_TABLE:
      REMOVE Centroid
      REMOVE Centroid.Easting
      REMOVE Centroid.Northing
      REMOVE StopArea.Abbreviation
      REMOVE StopArea.DefaultInterchangeDuration
      REMOVE StopArea.InterchangePriority
      REMOVE StopArea.Name
      REMOVE StopArea.Number
      REMOVE StopArea.ShortName
      REMOVE StopArea.Type
      REMOVE StopPoints.StopPoint.Designation
      REMOVE StopPoints.StopPoint.JourneyPatternPointNumber
      REMOVE StopPoints.StopPoint.Keys.Key{}.KeyValues.KeyValue
      REMOVE StopPoints.StopPoint.Keys.Key{}.KeyValues.KeyValue.Value
      REMOVE StopPoints.StopPoint.Keys.Key{}.TypeName
      REMOVE StopPoints.StopPoint.LengthMeters
      REMOVE StopPoints.StopPoint.LocalNumber
      REMOVE StopPoints.StopPoint.Location
      REMOVE StopPoints.StopPoint.Location.Easting
      REMOVE StopPoints.StopPoint.Location.Northing
      REMOVE StopPoints.StopPoint.Name
      REMOVE StopPoints.StopPoint.Orientation
      REMOVE StopPoints.StopPoint.Type
      REMOVE StopPoints.StopPoint.ZoneRefs.ZoneRef{}
      REMOVE StopPoints.StopPoint.ZoneRefs.ZoneRef{}.ZoneNumber
      REMOVE StopPoints.StopPoint.ZoneRefs.ZoneRef{}.ZoneType
      REMOVE StopPoints.StopPoint{}.Designation
      REMOVE StopPoints.StopPoint{}.JourneyPatternPointNumber
      REMOVE StopPoints.StopPoint{}.Keys.Key{}.KeyValues.KeyValue
      REMOVE StopPoints.StopPoint{}.Keys.Key{}.KeyValues.KeyValue.Value
      REMOVE StopPoints.StopPoint{}.Keys.Key{}.TypeName
      REMOVE StopPoints.StopPoint{}.LengthMeters
      REMOVE StopPoints.StopPoint{}.LocalNumber
      REMOVE StopPoints.StopPoint{}.Location
      REMOVE StopPoints.StopPoint{}.Location.Easting
      REMOVE StopPoints.StopPoint{}.Location.Northing
      REMOVE StopPoints.StopPoint{}.Name
      REMOVE StopPoints.StopPoint{}.Orientation
      REMOVE StopPoints.StopPoint{}.Type
      REMOVE StopPoints.StopPoint{}.ZoneRefs.ZoneRef{}
      REMOVE StopPoints.StopPoint{}.ZoneRefs.ZoneRef{}.ZoneNumber
      REMOVE StopPoints.StopPoint{}.ZoneRefs.ZoneRef{}.ZoneType
      REMOVE ValidDatePeriod
      REMOVE ValidDatePeriod.ValidFromDate
      REMOVE xml_fragment
      REMOVE xml_id
      REMOVE xml_matched_element
      REMOVE xml_parent_child_pos
      REMOVE xml_parent_id
      REMOVE fme_feature_type
      REMOVE N
      REMOVE E
      REMOVE Keys.Key{}.KeyValues.KeyValue
      REMOVE Keys.Key{}.KeyValues.KeyValue.Value
      REMOVE Keys.Key{}.TypeName
      REMOVE Location
      REMOVE Location.Easting
      REMOVE Location.Northing
      REMOVE StopPoint.Designation
      REMOVE StopPoint.JourneyPatternPointNumber
      REMOVE StopPoint.LengthMeters
      REMOVE StopPoint.LocalNumber
      REMOVE StopPoint.Name
      REMOVE StopPoint.Orientation
      REMOVE StopPoint.Type
      REMOVE ZoneRefs.ZoneRef{}
      REMOVE ZoneRefs.ZoneRef{}.ZoneNumber
      REMOVE ZoneRefs.ZoneRef{}.ZoneType
      REMOVE _overlaps
      REMOVE no_features
      SET_TO Allvarlighetsgrad = ERROR
      SET_TO TestTyp = StopPointHasInvalidCoordinate
      SET_TO sum = 0
    -> AttributeKeeper
AttributeManager_6
    ATTR_TABLE:
      REMOVE Centroid
      REMOVE Centroid.Easting
      REMOVE Centroid.Northing
      REMOVE StopArea.Abbreviation
      REMOVE StopArea.DefaultInterchangeDuration
      REMOVE StopArea.InterchangePriority
      REMOVE StopArea.Name
      REMOVE StopArea.ShortName
      REMOVE StopArea.Type
      REMOVE StopPoints.StopPoint.Designation
      REMOVE StopPoints.StopPoint.JourneyPatternPointNumber
      REMOVE StopPoints.StopPoint.Keys.Key{}.KeyValues.KeyValue
      REMOVE StopPoints.StopPoint.Keys.Key{}.KeyValues.KeyValue.Value
      REMOVE StopPoints.StopPoint.Keys.Key{}.TypeName
      REMOVE StopPoints.StopPoint.LengthMeters
      REMOVE StopPoints.StopPoint.LocalNumber
      REMOVE StopPoints.StopPoint.Location
      REMOVE StopPoints.StopPoint.Location.Easting
      REMOVE StopPoints.StopPoint.Location.Northing
      REMOVE StopPoints.StopPoint.Name
      REMOVE StopPoints.StopPoint.Orientation
      REMOVE StopPoints.StopPoint.Type
      REMOVE StopPoints.StopPoint.ZoneRefs.ZoneRef{}
      REMOVE StopPoints.StopPoint.ZoneRefs.ZoneRef{}.ZoneNumber
      REMOVE StopPoints.StopPoint.ZoneRefs.ZoneRef{}.ZoneType
      REMOVE StopPoints.StopPoint{}.Designation
      REMOVE StopPoints.StopPoint{}.JourneyPatternPointNumber
      REMOVE StopPoints.StopPoint{}.Keys.Key{}.KeyValues.KeyValue
      REMOVE StopPoints.StopPoint{}.Keys.Key{}.KeyValues.KeyValue.Value
      REMOVE StopPoints.StopPoint{}.Keys.Key{}.TypeName
      REMOVE StopPoints.StopPoint{}.LengthMeters
      REMOVE StopPoints.StopPoint{}.LocalNumber
      REMOVE StopPoints.StopPoint{}.Location
      REMOVE StopPoints.StopPoint{}.Location.Easting
      REMOVE StopPoints.StopPoint{}.Location.Northing
      REMOVE StopPoints.StopPoint{}.Name
      REMOVE StopPoints.StopPoint{}.Orientation
      REMOVE StopPoints.StopPoint{}.Type
      REMOVE StopPoints.StopPoint{}.ZoneRefs.ZoneRef{}
      REMOVE StopPoints.StopPoint{}.ZoneRefs.ZoneRef{}.ZoneNumber
      REMOVE StopPoints.StopPoint{}.ZoneRefs.ZoneRef{}.ZoneType
      REMOVE ValidDatePeriod
      REMOVE ValidDatePeriod.ValidFromDate
      REMOVE xml_fragment
      REMOVE xml_id
      REMOVE xml_matched_element
      REMOVE xml_parent_child_pos
      REMOVE xml_parent_id
      REMOVE fme_feature_type
      REMOVE N
      REMOVE E
      REMOVE Keys.Key{}.KeyValues.KeyValue
      REMOVE Keys.Key{}.KeyValues.KeyValue.Value
      REMOVE Keys.Key{}.TypeName
      REMOVE Location
      RENAME_SET_VALUE StopPoint.Name > Hållplatslägesnamn
      RENAME_SET_VALUE StopPoint.Designation > Hållplatsläge
      RENAME_SET_VALUE Location.Easting > HållplatslägeKoordinatÖstlig
      RENAME_SET_VALUE Location.Northing > HållplatslägeKoordinatNordlig
      RENAME_SET_VALUE StopPoint.JourneyPatternPointNumber > Hållplatslägesnummer
      REMOVE StopPoint.LengthMeters
      REMOVE StopPoint.LocalNumber
      REMOVE StopPoint.Orientation
      RENAME_SET_VALUE StopPoint.Type > Hållplatslägestyp
      REMOVE ZoneRefs.ZoneRef{}
      REMOVE ZoneRefs.ZoneRef{}.ZoneNumber
      REMOVE ZoneRefs.ZoneRef{}.ZoneType
      REMOVE _overlaps
      RENAME_SET_VALUE StopArea.Number > Hållplatsnummer
      SET_TO Allvarlighetsgrad = ERROR
      SET_TO TestTyp = StopPointHasInvalidCoordinate
      SET_TO Felmeddelande = Hållplatsläge @Value(Hållplatslägesnamn) @Value(Hållplatsläge) med ID: @Value(Hållplatslägesnummer) har felaktig koordinat (@Value(HållplatslägeKoordinatÖstlig), @Value(HållplatslägeKoordinatNordlig))
      SET_TO sum = 1
    -> ExcelStyler_3
ExcelStyler_3
    ATTRS_TO_STYLE = Allvarlighetsgrad
    BACKGROUND_COLOR = FME_CONDITIONAL:DEFAULT_VALUE''BOOL_OP;OR;COMPOSITE_TEST;1;TEST @Value(Allvarlighetsgrad) = WARNING'1,0.827451,0.529412'BOOL_OP;OR;COMPOSITE_TEST;1;TEST @Value(Allvarlighetsgrad) = ERROR'1,0.501961,0.501961'FME_NUM_CONDITIONS3___
    ROW_OR_CELL = cell
    ExcelStyled -> StopPointHasInvalidCoordinate (writer XLSXW_1)
    ExcelStyled -> AttributeKeeper
NoFeaturesTester_2
    NOINPUT -> AttributeManager_10
    -> AttributeManager_7
AttributeManager_10
    ATTR_TABLE:
      REMOVE Centroid
      REMOVE StopArea.Abbreviation
      REMOVE StopArea.DefaultInterchangeDuration
      REMOVE StopArea.InterchangePriority
      REMOVE StopArea.Name
      REMOVE StopArea.Number
      REMOVE Centroid.Easting
      REMOVE Centroid.Northing
      REMOVE StopArea.ShortName
      REMOVE StopArea.Type
      REMOVE StopPoints.StopPoint.Designation
      REMOVE StopPoints.StopPoint.JourneyPatternPointNumber
      REMOVE StopPoints.StopPoint.Keys.Key{}.KeyValues.KeyValue
      REMOVE StopPoints.StopPoint.Keys.Key{}.KeyValues.KeyValue.Value
      REMOVE StopPoints.StopPoint.Keys.Key{}.TypeName
      REMOVE StopPoints.StopPoint.LengthMeters
      REMOVE StopPoints.StopPoint.LocalNumber
      REMOVE StopPoints.StopPoint.Location
      REMOVE StopPoints.StopPoint.Location.Easting
      REMOVE StopPoints.StopPoint.Location.Northing
      REMOVE StopPoints.StopPoint.Name
      REMOVE StopPoints.StopPoint.Orientation
      REMOVE StopPoints.StopPoint.Type
      REMOVE StopPoints.StopPoint.ZoneRefs.ZoneRef{}
      REMOVE StopPoints.StopPoint.ZoneRefs.ZoneRef{}.ZoneNumber
      REMOVE StopPoints.StopPoint.ZoneRefs.ZoneRef{}.ZoneType
      REMOVE StopPoints.StopPoint{}.Designation
      REMOVE StopPoints.StopPoint{}.JourneyPatternPointNumber
      REMOVE StopPoints.StopPoint{}.Keys.Key{}.KeyValues.KeyValue
      REMOVE StopPoints.StopPoint{}.Keys.Key{}.KeyValues.KeyValue.Value
      REMOVE StopPoints.StopPoint{}.Keys.Key{}.TypeName
      REMOVE StopPoints.StopPoint{}.LengthMeters
      REMOVE StopPoints.StopPoint{}.LocalNumber
      REMOVE StopPoints.StopPoint{}.Location
      REMOVE StopPoints.StopPoint{}.Location.Easting
      REMOVE StopPoints.StopPoint{}.Location.Northing
      REMOVE StopPoints.StopPoint{}.Name
      REMOVE StopPoints.StopPoint{}.Orientation
      REMOVE StopPoints.StopPoint{}.Type
      REMOVE StopPoints.StopPoint{}.ZoneRefs.ZoneRef{}
      REMOVE StopPoints.StopPoint{}.ZoneRefs.ZoneRef{}.ZoneNumber
      REMOVE StopPoints.StopPoint{}.ZoneRefs.ZoneRef{}.ZoneType
      REMOVE ValidDatePeriod
      REMOVE ValidDatePeriod.ValidFromDate
      REMOVE xml_fragment
      REMOVE xml_id
      REMOVE xml_matched_element
      REMOVE xml_parent_child_pos
      REMOVE xml_parent_id
      REMOVE fme_feature_type
      REMOVE N
      REMOVE E
      REMOVE Keys.Key{}.KeyValues.KeyValue
      REMOVE Keys.Key{}.KeyValues.KeyValue.Value
      REMOVE Keys.Key{}.TypeName
      REMOVE Location
      REMOVE Location.Easting
      REMOVE Location.Northing
      REMOVE StopPoint.Designation
      REMOVE StopPoint.JourneyPatternPointNumber
      REMOVE StopPoint.LengthMeters
      REMOVE StopPoint.LocalNumber
      REMOVE StopPoint.Name
      REMOVE StopPoint.Orientation
      REMOVE StopPoint.Type
      REMOVE ZoneRefs.ZoneRef{}
      REMOVE ZoneRefs.ZoneRef{}.ZoneNumber
      REMOVE ZoneRefs.ZoneRef{}.ZoneType
      REMOVE _overlaps
      SET_TO Allvarlighetsgrad = ERROR
      SET_TO TestTyp = StopAreaHasInvalidCoordinate
      REMOVE no_features
      SET_TO sum = 0
    -> AttributeKeeper
AttributeManager_7
    ATTR_TABLE:
      REMOVE Centroid
      REMOVE StopArea.Abbreviation
      REMOVE StopArea.DefaultInterchangeDuration
      REMOVE StopArea.InterchangePriority
      RENAME_SET_VALUE StopArea.Name > Hållplatsnamn
      RENAME_SET_VALUE StopArea.Number > Hållplatsnummer
      RENAME_SET_VALUE Centroid.Easting > CentrumkoordinatÖstlig
      RENAME_SET_VALUE Centroid.Northing > CentrumkoordinatNordlig
      REMOVE StopArea.ShortName
      REMOVE StopArea.Type
      REMOVE StopPoints.StopPoint.Designation
      REMOVE StopPoints.StopPoint.JourneyPatternPointNumber
      REMOVE StopPoints.StopPoint.Keys.Key{}.KeyValues.KeyValue
      REMOVE StopPoints.StopPoint.Keys.Key{}.KeyValues.KeyValue.Value
      REMOVE StopPoints.StopPoint.Keys.Key{}.TypeName
      REMOVE StopPoints.StopPoint.LengthMeters
      REMOVE StopPoints.StopPoint.LocalNumber
      REMOVE StopPoints.StopPoint.Location
      REMOVE StopPoints.StopPoint.Location.Easting
      REMOVE StopPoints.StopPoint.Location.Northing
      REMOVE StopPoints.StopPoint.Name
      REMOVE StopPoints.StopPoint.Orientation
      REMOVE StopPoints.StopPoint.Type
      REMOVE StopPoints.StopPoint.ZoneRefs.ZoneRef{}
      REMOVE StopPoints.StopPoint.ZoneRefs.ZoneRef{}.ZoneNumber
      REMOVE StopPoints.StopPoint.ZoneRefs.ZoneRef{}.ZoneType
      REMOVE StopPoints.StopPoint{}.Designation
      REMOVE StopPoints.StopPoint{}.JourneyPatternPointNumber
      REMOVE StopPoints.StopPoint{}.Keys.Key{}.KeyValues.KeyValue
      REMOVE StopPoints.StopPoint{}.Keys.Key{}.KeyValues.KeyValue.Value
      REMOVE StopPoints.StopPoint{}.Keys.Key{}.TypeName
      REMOVE StopPoints.StopPoint{}.LengthMeters
      REMOVE StopPoints.StopPoint{}.LocalNumber
      REMOVE StopPoints.StopPoint{}.Location
      REMOVE StopPoints.StopPoint{}.Location.Easting
      REMOVE StopPoints.StopPoint{}.Location.Northing
      REMOVE StopPoints.StopPoint{}.Name
      REMOVE StopPoints.StopPoint{}.Orientation
      REMOVE StopPoints.StopPoint{}.Type
      REMOVE StopPoints.StopPoint{}.ZoneRefs.ZoneRef{}
      REMOVE StopPoints.StopPoint{}.ZoneRefs.ZoneRef{}.ZoneNumber
      REMOVE StopPoints.StopPoint{}.ZoneRefs.ZoneRef{}.ZoneType
      REMOVE ValidDatePeriod
      REMOVE ValidDatePeriod.ValidFromDate
      REMOVE xml_fragment
      REMOVE xml_id
      REMOVE xml_matched_element
      REMOVE xml_parent_child_pos
      REMOVE xml_parent_id
      REMOVE fme_feature_type
      REMOVE N
      REMOVE E
      REMOVE Keys.Key{}.KeyValues.KeyValue
      REMOVE Keys.Key{}.KeyValues.KeyValue.Value
      REMOVE Keys.Key{}.TypeName
      REMOVE Location
      REMOVE Location.Easting
      REMOVE Location.Northing
      REMOVE StopPoint.Designation
      REMOVE StopPoint.JourneyPatternPointNumber
      REMOVE StopPoint.LengthMeters
      REMOVE StopPoint.LocalNumber
      REMOVE StopPoint.Name
      REMOVE StopPoint.Orientation
      REMOVE StopPoint.Type
      REMOVE ZoneRefs.ZoneRef{}
      REMOVE ZoneRefs.ZoneRef{}.ZoneNumber
      REMOVE ZoneRefs.ZoneRef{}.ZoneType
      REMOVE _overlaps
      SET_TO Allvarlighetsgrad = ERROR
      SET_TO TestTyp = StopAreaHasInvalidCoordinate
      SET_TO Felmeddelande = Hållplats @Value(Hållplatsnamn) med ID: @Value(Hållplatsnummer) har felaktig koordinat (@Value(CentrumkoordinatÖstlig), @Value(CentrumkoordinatNordlig))
      SET_TO sum = 1
    -> ExcelStyler_5
ExcelStyler_5
    ATTRS_TO_STYLE = Allvarlighetsgrad
    BACKGROUND_COLOR = FME_CONDITIONAL:DEFAULT_VALUE''BOOL_OP;OR;COMPOSITE_TEST;1;TEST @Value(Allvarlighetsgrad) = WARNING'1,0.827451,0.529412'BOOL_OP;OR;COMPOSITE_TEST;1;TEST @Value(Allvarlighetsgrad) = ERROR'1,0.501961,0.501961'FME_NUM_CONDITIONS3___
    ROW_OR_CELL = cell
    ExcelStyled -> StopAreaHasInvalidCoordinate (writer XLSXW_1)
    ExcelStyled -> AttributeKeeper

Bookmark: Writers
StopPointHasInvalidCoordinate (writer XLSXW_1)
    attributes: Allvarlighetsgrad string(15), Felmeddelande string(100), Hållplatslägesnamn string(41), Hållplatsläge string(10), HållplatslägeKoordinatÖstlig number(20), HållplatslägeKoordinatNordlig number(20), Hållplatslägesnummer number(20), Hållplatslägestyp string(9), Hållplatsnummer number(20), TestTyp string(30), Allvarlighetsgrad.formatting string(200)
StopAreaHasInvalidCoordinate (writer XLSXW_1)
    attributes: Allvarlighetsgrad string(15), Felmeddelande string(100), Hållplatsnamn string(41), Hållplatsnummer number(20), CentrumkoordinatÖstlig number(20), CentrumkoordinatNordlig number(20), TestTyp string(30), Allvarlighetsgrad.formatting string(200)

Bookmark: Witers
RouteLinkSpeedTooHigh (writer XLSXW_1)
    attributes: Allvarlighetsgrad string(20), Felmeddelande string(110), Beräknad_Medelhastighet_Körlänk string(25), Linje number(20), Turnummer number(20), Från_HållplatsId string(20), Till_HållplatsId string(20), Avgångstid string(20), Ankomsttid string(20), Längd_Körlänk number(20), Hastighetsbegränsning_Rebus_Körlänk number(20), Planerad_Körtid string(20), TestTyp string(20), sum string(20), Allvarlighetsgrad.formatting string(20)

Bookmark: Check which transaction method is used in the export. DEFINE truncates Pubtrans an Modify only updates geoemtries.
Creator
    GEOMTYPE = Geometry Object
    NUM = 1
    CREATED -> XMLXQueryExtractor
XMLXQueryExtractor
    NEW_ATTRIBUTES = ModificationType
    QUERY_EXPR:
      declare namespace x='http://www.pubtrans.com/DII/3.0';

      string(//x:NetworkVersion/@ModificationType)
    RESULT_ATTRIBUTE = _result
    RESULT_TYPE_NAME = Separated values
    SEPARATOR_VALUE = ,
    WRITE_XML_HEADER = No
    XML_FILE = $(DEFINE_NET_INPUT)
    XML_TYPE = XML file
    XQUERY_TYPE = XQuery expression
    QUERY_RESULTS -> AttributeFilter_3
AttributeFilter_3
    ATTR_NAME = _result
    ATTR_VALUES = <Empty>,<Missing>,<Null>,<Unfiltered>,DEFINE,MODIFY
    DEFINE -> AttributeManager_13
    MODIFY -> AttributeManager_14
AttributeManager_13
    ATTR_TABLE:
      SET_TO Allvarlighetsgrad = WARNING
      SET_TO TestTyp = TransactionMethodIsDefine
    -> AttributeKeeper
AttributeManager_14
    ATTR_TABLE:
      SET_TO Allvarlighetsgrad = INFO
      SET_TO TestTyp = TransactionMethodIsModify
    -> AttributeKeeper

Bookmark: Write summary to excel
AttributeKeeper
    CREATE_BULK_MODE_FEATURES = NO
    KEEP_ATTRS = Allvarlighetsgrad,TestTyp,sum
    -> StatisticsCalculator
StatisticsCalculator
    CALCULATION_MODE = NUMERIC
    FEAT_STATS = sum,NUMERIC_MODE,,,,SUM,,,,,,,,
    GROUP_BY = Allvarlighetsgrad TestTyp
    SUMMARY -> AttributeManager_8
AttributeManager_8
    ATTR_TABLE:
      SET_TO Förklaring = FME_CONDITIONAL:DEFAULT_VALUE'_FME_NO_OP_'BOOL_OP;AND;COMPOSITE_TEST;1 AND 2;TEST @Value(TestTyp) = StopPointsIsWithinDistanceOfStopArea;TEST @Value(Allvarlighetsgrad) = ERROR'Testar om hållplatsläge är inom $(ErrorDistanceSAToSP) meter från hållplatsens centrumkoordinat.'BOOL_OP;AND;COMPOSITE_TEST;1 AND 2;TEST @Value(TestTyp) = StopPointsIsWithinDistanceOfStopArea;TEST @Value(Allvarlighetsgrad) = WARNING'Testar om hållplatsläge är inom $(WarningDistanceSAToSP) meter från hållplatsens centrumkoordinat.'BOOL_OP;OR;COMPOSITE_TEST;1;TEST @Value(TestTyp) = StopPointHasInvalidCoordinate'Testar om hållplatsläge har inkorrekt koordinat. En inkorrekt koordinat är en koordinat som ligger utanför en fördefinierad ruta över södra sverige.'BOOL_OP;OR;COMPOSITE_TEST;1;TEST @Value(TestTyp) = StopAreaHasInvalidCoordinate'Testar om hållplats (centrumkoordiant) har inkorrekt koordinat. En inkorrekt koordinat är en koordinat som ligger utanför en fördefinierad ruta över södra sverige.'BOOL_OP;OR;COMPOSITE_TEST;1;TEST @Value(TestTyp) = TransactionMethodIsModify'Transaktionsmetod är MODIFY. Detta betyder att denna export endast uppdaterar eller lägger till dessa geoemtrier i Pubtrans.'BOOL_OP;OR;COMPOSITE_TEST;1;TEST @Value(TestTyp) = TransactionMethodIsDefine'Transaktionsmetod är DEFINE. Detta betyder att denna export kommer ersätta ALLA geometrier i Pubtrans.'BOOL_OP;AND;COMPOSITE_TEST;1 AND 2;TEST @Value(TestTyp) = AverageSpeedForRouteLinkTooHigh;TEST @Value(Allvarlighetsgrad) = WARNING'Testar om en körlänk på en tur har mer eller lika med $(WarningSpeedRouteLink)  och mindre än $(ErrorSpeedRouteLink) km/h i medelhastighet. Beräkningen är baserad på körlänkens längd och körtiden.'BOOL_OP;AND;COMPOSITE_TEST;1 AND 2;TEST @Value(TestTyp) = AverageSpeedForRouteLinkTooHigh;TEST @Value(Allvarlighetsgrad) = ERROR'Testar om en körlänk på en tur har mer eller lika med $(ErrorSpeedRouteLink) km/h i medelhastighet. Beräkningen är baserad på körlänkens längd och körtiden.'FME_NUM_CONDITIONS9___
      RENAME_SET_VALUE sum.sum > AntalFelaktigaObjekt
    -> ExcelStyler
ExcelStyler
    ATTRS_TO_STYLE = AntalFelaktigaObjekt
    BACKGROUND_COLOR = FME_CONDITIONAL:DEFAULT_VALUE'0,0.666667,0'BOOL_OP;AND;COMPOSITE_TEST;1 AND 2;TEST @Value(AntalFelaktigaObjekt) > 0;TEST @Value(Allvarlighetsgrad) = ERROR'1,0,0'BOOL_OP;AND;COMPOSITE_TEST;1 AND 2;TEST @Value(AntalFelaktigaObjekt) > 0;TEST @Value(Allvarlighetsgrad) = WARNING'1,0.666667,0'BOOL_OP;OR;COMPOSITE_TEST;1;TEST @Value(TestTyp) = TransactionMethodIsDefine'1,0,0'FME_NUM_CONDITIONS4___
    FONT_NAME = MS Shell Dlg 2,9,BOLD
    ROW_OR_CELL = cell
    ExcelStyled -> FeatureHolder
FeatureHolder
    -> Summering (writer XLSXW_1)

Bookmark: Witers
Summering (writer XLSXW_1)
    attributes: Allvarlighetsgrad string(20), TestTyp string(38), AntalFelaktigaObjekt number(20), Förklaring string(200), AntalFelaktigaObjekt.formatting string(200)
